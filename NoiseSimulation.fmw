FME workspace NoiseSimulation.fmw

Parameters:
- SourceDataset_CITYGML = D:\MasterThesis\demo_data\malmo_3cim_ver_2_20220710\malmo_3cim_ver_2_20220710\malmo_3cim_ver_2_20220710.gml   # Source CityGML File(s)
- DestDataset_SHAPEFILE_10 = D:\MasterThesis\demo_data\TransFormats\3cim_ade_shp.shp   # Destination Esri Shapefile Folder
- DestDataset_SHAPEFILE_8 = D:\MasterThesis\demo_data\TransFormats\3cim_ade_shp.shp   # Destination Esri Shapefile Folder
- DestDataset_SHAPEFILE = D:\MasterThesis\demo_data\TransFormats\3cim_ade_shp.shp   # Destination Esri Shapefile Folder
- DestDataset_SHAPEFILE_12 = D:\MasterThesis\demo_data\TransFormats\3cim_ade_shp.shp   # Destination Esri Shapefile Folder
- DestDataset_SHAPEFILE_9 = D:\MasterThesis\demo_data\TransFormats\3cim_ade_shp.shp   # Destination Esri Shapefile Folder
- DestDataset_ESRIASCIIGRID = D:\MasterThesis\demo_data\TransFormats   # Destination Esri ASCII Grid Folder
- SourceDataset_GEOTIFF_3 = D:\MasterThesis\demo_data\Geotiff\Geotiff\DEM_Terrain_1m.tif   # Source GeoTIFF File(s) or URL(s)
- SourceDataset_SHAPEFILE_2 = D:\MasterThesis\demo_data\RoadDataset\malmöbilflöde_uppskattning_20\malmöbilflöde_uppskattning_20.shp   # Source Esri Shapefile(s)
- DestDataset_SHAPEFILE_11 = D:\MasterThesis\demo_data\TransFormats\3cim_ade_shp.shp   # Destination Esri Shapefile Folder
- SourceDataset_SHAPEFILE = D:\MasterThesis\demo_data\RoadDataset\malmöbilflöde_uppskattning_20\malmöbilflöde_uppskattning_20.shp   # Source Esri Shapefile(s)

Readers:
- CITYGML_1: CITYGML from $(SourceDataset_CITYGML)
- GEOTIFF_2: GEOTIFF from $(SourceDataset_GEOTIFF_3)
- SHAPEFILE_8: SHAPEFILE from $(SourceDataset_SHAPEFILE_2) in SWEREF-99-13-30
- SHAPEFILE_1: SHAPEFILE from $(SourceDataset_SHAPEFILE)

Writers:
- SHAPEFILE_2: SHAPEFILE to $(DestDataset_SHAPEFILE)
- SHAPEFILE_3: SHAPEFILE to $(DestDataset_SHAPEFILE_10)
- SHAPEFILE_4: SHAPEFILE to $(DestDataset_SHAPEFILE_8)
- SHAPEFILE_5: SHAPEFILE to $(DestDataset_SHAPEFILE_12)
- SHAPEFILE_6: SHAPEFILE to $(DestDataset_SHAPEFILE_9)
- ESRIASCIIGRID_1: ESRIASCIIGRID to $(DestDataset_ESRIASCIIGRID)
- SHAPEFILE_7: SHAPEFILE to $(DestDataset_SHAPEFILE_11)

malmöbilflöde_uppskattning_20 (reader SHAPEFILE_1)
    attributes: GID number(11,0), GK_IDVAG number(11,0), NAMN varchar(107), LENGTH number(31,15), TYP_15 long, TYP_21 long, TYP_NAMN varchar(200), ÖVRIGA varchar(200), DATAKÄLLA varchar(200), DATA_ID number(11,0), DATA_ÅR long, MVD_10 number(11,0), MVD_15 number(11,0), MVD_20 number(11,0), DAG_20 number(11,0), KVÄLL_20 number(11,0), NATT_20 number(11,0), ÅDT_20 number(11,0), TUNG_10 number(11,0), TUNG_15 number(11,0), TUNG_20 number(11,0), HAST_15 number(11,0), HAST_21 number(11,0), TIMESTAMP varchar(21), tr_arb_15 double, tr_arb_20 float, tr_arb_10T double, tr_arb_10 float, tr_arb_15T float, tr_arb_20T float
    -> Reprojector
Reprojector
    DEST = SWEREF-99-13-30
    INTERPOLATION_TYPE_NAME = Nearest Neighbor
    RASTER_CELL_SIZE = Preserve Cells
    RASTER_TOLERANCE = 0.0
    SOURCE = SWEREF-99-TM
    REPROJECTED -> KVALL_20
KVALL_20: AttributeCreator
    ATTR_TABLE:
      SET_TO KVALL_20 = @Evaluate(@round(@Value(MVD_20)*0.17/10,0)*10
        )
    -> RoadAttributeCalculator
RoadAttributeCalculator: AttributeCreator
    ATTR_TABLE:
      SET_TO veh_h_d = @Evaluate(@Value(DAG_20)/12)
      SET_TO veh_h_e = @Evaluate(@Value(KVALL_20)/4)
      SET_TO veh_h_n = @Evaluate(@Value(NATT_20)/8)
      SET_TO k_d = @Evaluate(@Value(DAG_20)/12/@Value(MVD_20))
      SET_TO k_e = @Evaluate(@Value(KVALL_20)/4/@Value(MVD_20))
      SET_TO k_n = @Evaluate(@Value(NATT_20)/8/@Value(MVD_20))
      SET_TO speed_d = @Value(HAST_21)
      SET_TO speed_e = @Value(HAST_21)
      SET_TO speed_n = @Value(HAST_21)
      SET_TO H1 = 20
    -> RoadClipper [CANDIDATE]
GEOTIFF (reader GEOTIFF_2)
    -> RasterCellValueReplacer
    -> DEM_ASCII (writer ESRIASCIIGRID_1)
DEM_ASCII (writer ESRIASCIIGRID_1)
RasterCellValueReplacer
    RANGE_TABLE = 0,999,1
    REPLACE_NODATA = DoNotReplaceNodata
    -> StudyAreaBoundary
StudyAreaBoundary: RasterToPolygonCoercer
    EXTRACT_NODATA = No
    LABEL_ATTRIBUTE = _label
    PRESERVE_ATTRIBUTES = Yes
    POLYGONS -> RoadClipper [CLIPPER]
    POLYGONS -> AuxTraffic_Clipper [CLIPPER]
    POLYGONS -> CF_Clipper [CLIPPER]
    POLYGONS -> BP_Clipper [CLIPPER]
    POLYGONS -> SV_Clipper [CLIPPER]
    POLYGONS -> PC_Clipper [CLIPPER]
RoadClipper: Clipper
    BOUNDARY_CASES = INSIDE
    CLEANING_TOLERANCE = 0.01
    CLIPPED_ATTR = _clipped
    GENERATE_LIST = NO
    INVALID_PARTS_HANDLING = REJECT_WHOLE
    MISSING_M_MODE = Linear Interpolation
    MISSING_Z_MODE = Planar Interpolation
    MULTIPLE_CLIPPERS = NO
    M_VAL_SOURCE = CANDIDATE
    PRESERVE_RASTER_EXTENTS = NO
    RASTER_CELL_MODE = CENTER
    Z_VAL_SOURCE = CANDIDATE
    INSIDE -> Road_clip (writer SHAPEFILE_6)
Road_clip (writer SHAPEFILE_6)
    attributes: GID varchar(100), NAMN varchar(107), MVD_20 number(20,10), TUNG_20 number(20,10), veh_h_d number(20,10), veh_h_e number(20,10), veh_h_n number(20,10), k_d number(20,10), k_e number(20,10), k_n number(20,10), speed_d number(20,10), speed_e number(20,10), speed_n number(20,10)
AuxiliaryTrafficArea (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), trecim_geometry_metadata{}.trecim_tidpunkt_for_lagesbestamning xml_datetime, trecim_geometry_metadata{}.trecim_tidpunkt_for_kontroll_av_geometri xml_datetime, trecim_geometry_metadata{}.trecim_lagesbestamningsmetod_iplan_trecim_typ xml_buffer, trecim_geometry_metadata{}.trecim_lagesbestamningsmetod_iplan_trecim_typ_codeSpace xml_buffer, trecim_geometry_metadata{}.trecim_lagesbestamningsmetod_iplan_trecim_tidperiod_for_underlagets_framtagande_trecim_fran xml_datetime, trecim_geometry_metadata{}.trecim_lagesbestamningsmetod_iplan_trecim_tidperiod_for_underlagets_framtagande_trecim_till xml_datetime, trecim_geometry_metadata{}.trecim_lagesbestamningsmetod_ihojd_trecim_typ xml_buffer, trecim_geometry_metadata{}.trecim_lagesbestamningsmetod_ihojd_trecim_typ_codeSpace xml_buffer, trecim_geometry_metadata{}.trecim_lagesbestamningsmetod_ihojd_trecim_tidperiod_for_underlagets_framtagande_trecim_fran xml_datetime, trecim_geometry_metadata{}.trecim_lagesbestamningsmetod_ihojd_trecim_tidperiod_for_underlagets_framtagande_trecim_till xml_datetime, trecim_geometry_metadata{}.trecim_osakertlage xml_buffer, trecim_geometry_metadata{}.trecim_osakertlage_codeSpace xml_buffer, trecim_geometry_metadata{}.trecim_absolut_lagesosakerhet_plan xml_real32, trecim_geometry_metadata{}.trecim_absolut_lagesosakerhet_hojd xml_real32, citygml_class xml_buffer, citygml_class_codeSpace xml_buffer,
      citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, trecim_auxiliary_traffic_area{}.trecim_id xml_buffer, trecim_auxiliary_traffic_area{}.trecim_version xml_int64
    -> CoorSwapper_Aux
CoorSwapper_Aux: CoordinateSwapper
    SWAP_TYPE = X <-> Y
    -> 2DForcer_Aux
2DForcer_Aux
    2D -> Counter_Aux
Counter_Aux
    CNT_ATTR = id
    DOMAIN = counter
    SCOPE = Global
    START = 0
    -> GroundClass_Aux
GroundClass_Aux: AttributeCreator
    ATTR_TABLE = SET_TO cnossos_cla = FME_CONDITIONAL:DEFAULT_VALUE'FME_NULL_VALUE'BOOL_OP;OR;COMPOSITE_TEST;1;TEST @Value(citygml_surface_material_codeSpace) = 10000'G'BOOL_OP;OR;COMPOSITE_TEST;1;TEST @Value(citygml_surface_material_codeSpace) = 10001'G'BOOL_OP;OR;COMPOSITE_TEST;1;TEST @Value(citygml_surface_material_codeSpace) = 10009'C'FME_NUM_CONDITIONS4___
    -> GroundFactor_Aux
GroundFactor_Aux: AttributeCreator
    ATTR_TABLE = SET_TO ground_fac = FME_CONDITIONAL:DEFAULT_VALUE'_FME_NO_OP_'BOOL_OP;OR;COMPOSITE_TEST;1;TEST @Value(cnossos_cla) = A'1'BOOL_OP;OR;COMPOSITE_TEST;1;TEST @Value(cnossos_cla) = B'1'BOOL_OP;OR;COMPOSITE_TEST;1;TEST @Value(cnossos_cla) = C'1'BOOL_OP;OR;COMPOSITE_TEST;1;TEST @Value(cnossos_cla) = D'1'BOOL_OP;OR;COMPOSITE_TEST;1;TEST @Value(cnossos_cla) = E'0.7'BOOL_OP;OR;COMPOSITE_TEST;1;TEST @Value(cnossos_cla) = F'0.3'BOOL_OP;OR;COMPOSITE_TEST;1;TEST @Value(cnossos_cla) = G'0'BOOL_OP;OR;COMPOSITE_TEST;1;TEST @Value(cnossos_cla) = H'0'FME_NUM_CONDITIONS9___
    -> AuxTraffic_Clipper [CANDIDATE]
AuxTraffic_Clipper: Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AuxTraffic_clip (writer SHAPEFILE_2)
AuxTraffic_clip (writer SHAPEFILE_2)
    attributes: id number(10,0), gml_name varchar(254), gr_cla varchar(20), gr_fac number(20,10)
CityFurniture (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), trecim_geometry_metadata{}.trecim_tidpunkt_for_lagesbestamning xml_datetime, trecim_geometry_metadata{}.trecim_tidpunkt_for_kontroll_av_geometri xml_datetime, trecim_geometry_metadata{}.trecim_lagesbestamningsmetod_iplan_trecim_typ xml_buffer, trecim_geometry_metadata{}.trecim_lagesbestamningsmetod_iplan_trecim_typ_codeSpace xml_buffer, trecim_geometry_metadata{}.trecim_lagesbestamningsmetod_iplan_trecim_tidperiod_for_underlagets_framtagande_trecim_fran xml_datetime, trecim_geometry_metadata{}.trecim_lagesbestamningsmetod_iplan_trecim_tidperiod_for_underlagets_framtagande_trecim_till xml_datetime, trecim_geometry_metadata{}.trecim_lagesbestamningsmetod_ihojd_trecim_typ xml_buffer, trecim_geometry_metadata{}.trecim_lagesbestamningsmetod_ihojd_trecim_typ_codeSpace xml_buffer, trecim_geometry_metadata{}.trecim_lagesbestamningsmetod_ihojd_trecim_tidperiod_for_underlagets_framtagande_trecim_fran xml_datetime, trecim_geometry_metadata{}.trecim_lagesbestamningsmetod_ihojd_trecim_tidperiod_for_underlagets_framtagande_trecim_till xml_datetime, trecim_geometry_metadata{}.trecim_osakertlage xml_buffer, trecim_geometry_metadata{}.trecim_osakertlage_codeSpace xml_buffer, trecim_geometry_metadata{}.trecim_absolut_lagesosakerhet_plan xml_real32, trecim_geometry_metadata{}.trecim_absolut_lagesosakerhet_hojd xml_real32, citygml_class xml_buffer, citygml_class_codeSpace xml_buffer,
      citygml_function{} xml_buffer, citygml_function{}.codeSpace xml_buffer, citygml_usage{} xml_buffer, citygml_usage{}.codeSpace xml_buffer, citygml_level_of_detail{} xml_buffer, trecim_city_furniture{}.trecim_id xml_buffer, trecim_city_furniture{}.trecim_version xml_int64, trecim_city_furniture{}.trecim_width xml_real64, trecim_city_furniture{}.trecim_relative_height xml_real64
    -> CoorSwapper_CF
CoorSwapper_CF: CoordinateSwapper
    SWAP_TYPE = X <-> Y
    -> 2DForcer_CF
2DForcer_CF
    2D -> Counter_CF
Counter_CF
    CNT_ATTR = id
    DOMAIN = counter
    SCOPE = Global
    START = 0
    -> WallFilter
WallFilter: TestFilter
    DEFAULT_VALUE = <UNFILTERED>
    PASSED_TEST_GROUP_OUTPUT = FIRST
    TEST_LIST = "BOOL_OP,OR,COMPOSITE_TEST,""""""1"""""",TEST_CLAUSE,TEST @Value(citygml_function{0}.codeSpace) = 51100",wall,"BOOL_OP,OR,COMPOSITE_TEST,""""""1"""""",TEST_CLAUSE,TEST @Value(citygml_function{0}.codeSpace) = 60100",wall
    wall -> WallHeight
WallHeight: AttributeCreator
    ATTR_TABLE:
      SET_TO height = FME_CONDITIONAL:DEFAULT_VALUE'_FME_NO_OP_'BOOL_OP;OR;COMPOSITE_TEST;1;TEST @Value(citygml_function{0}.codeSpace) = 51100'1'BOOL_OP;OR;COMPOSITE_TEST;1;TEST @Value(citygml_function{0}.codeSpace) = 60100'0.5'FME_NUM_CONDITIONS3___
      SET_TO abov_gr = 0
      SET_TO H1 = 20
    -> CF_Clipper [CANDIDATE]
CF_Clipper: Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> CityFurniture_clip (writer SHAPEFILE_3)
CityFurniture_clip (writer SHAPEFILE_3)
    attributes: id number(10,0), gml_name varchar(254), height number(20,10), abov_gr number(20,10)
PlantCover (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), trecim_geometry_metadata{}.trecim_tidpunkt_for_lagesbestamning xml_datetime, trecim_geometry_metadata{}.trecim_tidpunkt_for_kontroll_av_geometri xml_datetime, trecim_geometry_metadata{}.trecim_lagesbestamningsmetod_iplan_trecim_typ xml_buffer, trecim_geometry_metadata{}.trecim_lagesbestamningsmetod_iplan_trecim_typ_codeSpace xml_buffer, trecim_geometry_metadata{}.trecim_lagesbestamningsmetod_iplan_trecim_tidperiod_for_underlagets_framtagande_trecim_fran xml_datetime, trecim_geometry_metadata{}.trecim_lagesbestamningsmetod_iplan_trecim_tidperiod_for_underlagets_framtagande_trecim_till xml_datetime, trecim_geometry_metadata{}.trecim_lagesbestamningsmetod_ihojd_trecim_typ xml_buffer, trecim_geometry_metadata{}.trecim_lagesbestamningsmetod_ihojd_trecim_typ_codeSpace xml_buffer, trecim_geometry_metadata{}.trecim_lagesbestamningsmetod_ihojd_trecim_tidperiod_for_underlagets_framtagande_trecim_fran xml_datetime, trecim_geometry_metadata{}.trecim_lagesbestamningsmetod_ihojd_trecim_tidperiod_for_underlagets_framtagande_trecim_till xml_datetime, trecim_geometry_metadata{}.trecim_osakertlage xml_buffer, trecim_geometry_metadata{}.trecim_osakertlage_codeSpace xml_buffer, trecim_geometry_metadata{}.trecim_absolut_lagesosakerhet_plan xml_real32, trecim_geometry_metadata{}.trecim_absolut_lagesosakerhet_hojd xml_real32, trecim_vegetation_object{}.trecim_id xml_buffer, trecim_vegetation_object{}.trecim_version xml_int64,
      citygml_class xml_buffer, citygml_class_codeSpace xml_buffer, citygml_function{} xml_buffer, citygml_function{}.codeSpace xml_buffer, citygml_usage{} xml_buffer, citygml_usage{}.codeSpace xml_buffer, citygml_average_height xml_real64, citygml_average_height_units xml_buffer, citygml_level_of_detail{} xml_buffer, trecim_plant_cover{}.trecim_species_popular_name{} xml_buffer, trecim_plant_cover{}.trecim_species_popular_name{}.codeSpace xml_buffer
    -> CoorSwapper_PC
CoorSwapper_PC: CoordinateSwapper
    SWAP_TYPE = X <-> Y
    -> 2DForcer_PC
2DForcer_PC
    2D -> Counter_PC
Counter_PC
    CNT_ATTR = id
    DOMAIN = counter
    SCOPE = Global
    START = 0
    -> GroundClass_PC
GroundClass_PC: AttributeCreator
    ATTR_TABLE = SET_TO cnossos_cla = FME_CONDITIONAL:DEFAULT_VALUE'_FME_NO_OP_'BOOL_OP;OR;COMPOSITE_TEST;1;TEST @Value(citygml_function{0}.codeSpace) = 10100'C'BOOL_OP;OR;COMPOSITE_TEST;1;TEST @Value(citygml_function{0}.codeSpace) = 10200'D'FME_NUM_CONDITIONS3___
    -> GroundFactor_PC
GroundFactor_PC: AttributeCreator
    ATTR_TABLE = SET_TO ground_fac = FME_CONDITIONAL:DEFAULT_VALUE'_FME_NO_OP_'BOOL_OP;OR;COMPOSITE_TEST;1;TEST @Value(cnossos_cla) = A'1'BOOL_OP;OR;COMPOSITE_TEST;1;TEST @Value(cnossos_cla) = B'1'BOOL_OP;OR;COMPOSITE_TEST;1;TEST @Value(cnossos_cla) = C'1'BOOL_OP;OR;COMPOSITE_TEST;1;TEST @Value(cnossos_cla) = D'1'BOOL_OP;OR;COMPOSITE_TEST;1;TEST @Value(cnossos_cla) = E'0.7'BOOL_OP;OR;COMPOSITE_TEST;1;TEST @Value(cnossos_cla) = F'0.3'BOOL_OP;OR;COMPOSITE_TEST;1;TEST @Value(cnossos_cla) = G'0'BOOL_OP;OR;COMPOSITE_TEST;1;TEST @Value(cnossos_cla) = H'0'FME_NUM_CONDITIONS9___
    -> PC_Clipper [CANDIDATE]
PC_Clipper: Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> PlantCover_clip (writer SHAPEFILE_4)
PlantCover_clip (writer SHAPEFILE_4)
    attributes: id number(10,0), gml_name varchar(254), gr_cla varchar(254), gr_fac number(20,10)
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), trecim_geometry_metadata{}.trecim_tidpunkt_for_lagesbestamning xml_datetime, trecim_geometry_metadata{}.trecim_tidpunkt_for_kontroll_av_geometri xml_datetime, trecim_geometry_metadata{}.trecim_lagesbestamningsmetod_iplan_trecim_typ xml_buffer, trecim_geometry_metadata{}.trecim_lagesbestamningsmetod_iplan_trecim_typ_codeSpace xml_buffer, trecim_geometry_metadata{}.trecim_lagesbestamningsmetod_iplan_trecim_tidperiod_for_underlagets_framtagande_trecim_fran xml_datetime, trecim_geometry_metadata{}.trecim_lagesbestamningsmetod_iplan_trecim_tidperiod_for_underlagets_framtagande_trecim_till xml_datetime, trecim_geometry_metadata{}.trecim_lagesbestamningsmetod_ihojd_trecim_typ xml_buffer, trecim_geometry_metadata{}.trecim_lagesbestamningsmetod_ihojd_trecim_typ_codeSpace xml_buffer, trecim_geometry_metadata{}.trecim_lagesbestamningsmetod_ihojd_trecim_tidperiod_for_underlagets_framtagande_trecim_fran xml_datetime, trecim_geometry_metadata{}.trecim_lagesbestamningsmetod_ihojd_trecim_tidperiod_for_underlagets_framtagande_trecim_till xml_datetime, trecim_geometry_metadata{}.trecim_osakertlage xml_buffer, trecim_geometry_metadata{}.trecim_osakertlage_codeSpace xml_buffer, trecim_geometry_metadata{}.trecim_absolut_lagesosakerhet_plan xml_real32, trecim_geometry_metadata{}.trecim_absolut_lagesosakerhet_hojd xml_real32, citygml_class xml_buffer, citygml_class_codeSpace xml_buffer,
      citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, trecim_building{}.trecim_id xml_buffer, trecim_building{}.trecim_version xml_int64, trecim_building_part{}.trecim_status xml_buffer, trecim_building_part{}.trecim_status_codeSpace xml_buffer
    -> CoorSwapper_BP
CoorSwapper_BP: CoordinateSwapper
    SWAP_TYPE = X <-> Y
    -> BoundsExtractor
BoundsExtractor
    XMAX = _xmax
    XMIN = _xmin
    YMAX = _ymax
    YMIN = _ymin
    ZMAX = _zmax
    ZMIN = _zmin
    -> Counter_BP
Counter_BP
    CNT_ATTR = id
    DOMAIN = counter
    SCOPE = Global
    START = 0
    -> AttributeCreator_BP
AttributeCreator_BP
    ATTR_TABLE:
      SET_TO height = @Evaluate(@sub(@Value(_zmax),@Value(_zmin)))
      SET_TO H1 = 30
      SET_TO name_id = @Value(id)
    -> SurfaceFootprintReplacer
SurfaceFootprintReplacer
    OFFSET_Z = 0
    SHADOW_MODE = Overhead Shadow
    FOOTPRINT -> BP_Clipper [CANDIDATE]
BP_Clipper: Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BuildingPart_clip (writer SHAPEFILE_5)
BuildingPart_clip (writer SHAPEFILE_5)
    attributes: id number(10,0), gml_name varchar(254), height number(20,10), name_id varchar(254)
Note: Copyright (c) 2018, Lund University, All rights reserved. / This FME script was developed for transforming 3CIM data and the road database from Malmö Stad, Skåne, Sweden. The transformed data was used as the input data of SoundPLAN noise simulation software. Detailed clarification of this script can be found in the master thesis Noise Simulations based on 3D City Models (link). The script is allowed to used in further studies about the application of 3CIM in noise simulations or other fields. / Redistribution and use in source and binary forms, with or without modification, are permitted provided that the following conditions are met: / 1. Redistributions of source code must retain the above copyright notice, this list of conditions and the following disclaimer. / 2. Redistributions in binary form must reproduce the above copyright notice, this list of conditions and the following disclaimer in the documentation and/or other materials provided with the distribution. / 3. Neither the name of the copyright holder nor the names of its contributors may be used to endorse or promote products derived from this software without specific prior written permission. / THIS SOFTWARE IS PROVIDED BY THE COPYRIGHT-HOLDERS AND CONTRIBUTORS "AS IS" AND ANY EXPRESS OR IMPLIED WARRANTIES, INCLUDING, BUT NOT LIMITED TO, THE IMPLIED WARRANTIES OF MERCHANTABILITY AND FITNESS FOR A PARTICULAR PURPOSE ARE DISCLAIMED. IN NO EVENT SHALL THE COPYRIGHT HOLDER OR CONTRIBUTORS BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.
SolitaryVegetationObject (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), trecim_geometry_metadata{}.trecim_tidpunkt_for_lagesbestamning xml_datetime, trecim_geometry_metadata{}.trecim_tidpunkt_for_kontroll_av_geometri xml_datetime, trecim_geometry_metadata{}.trecim_lagesbestamningsmetod_iplan_trecim_typ xml_buffer, trecim_geometry_metadata{}.trecim_lagesbestamningsmetod_iplan_trecim_typ_codeSpace xml_buffer, trecim_geometry_metadata{}.trecim_lagesbestamningsmetod_iplan_trecim_tidperiod_for_underlagets_framtagande_trecim_fran xml_datetime, trecim_geometry_metadata{}.trecim_lagesbestamningsmetod_iplan_trecim_tidperiod_for_underlagets_framtagande_trecim_till xml_datetime, trecim_geometry_metadata{}.trecim_lagesbestamningsmetod_ihojd_trecim_typ xml_buffer, trecim_geometry_metadata{}.trecim_lagesbestamningsmetod_ihojd_trecim_typ_codeSpace xml_buffer, trecim_geometry_metadata{}.trecim_lagesbestamningsmetod_ihojd_trecim_tidperiod_for_underlagets_framtagande_trecim_fran xml_datetime, trecim_geometry_metadata{}.trecim_lagesbestamningsmetod_ihojd_trecim_tidperiod_for_underlagets_framtagande_trecim_till xml_datetime, trecim_geometry_metadata{}.trecim_osakertlage xml_buffer, trecim_geometry_metadata{}.trecim_osakertlage_codeSpace xml_buffer, trecim_geometry_metadata{}.trecim_absolut_lagesosakerhet_plan xml_real32, trecim_geometry_metadata{}.trecim_absolut_lagesosakerhet_hojd xml_real32, trecim_vegetation_object{}.trecim_id xml_buffer, trecim_vegetation_object{}.trecim_version xml_int64,
      citygml_class xml_buffer, citygml_class_codeSpace xml_buffer, citygml_function{} xml_buffer, citygml_function{}.codeSpace xml_buffer, citygml_usage{} xml_buffer, citygml_usage{}.codeSpace xml_buffer, citygml_species xml_buffer, citygml_species_codeSpace xml_buffer, citygml_height xml_real64, citygml_height_units xml_buffer, citygml_trunk_diameter xml_real64, citygml_trunk_diameter_units xml_buffer, citygml_crown_diameter xml_real64, citygml_crown_diameter_units xml_buffer, citygml_level_of_detail{} xml_buffer, trecim_solitary_vegetation_object{}.trecim_lower_crown_height xml_real64, trecim_solitary_vegetation_object{}.trecim_species_popular_name xml_buffer, trecim_solitary_vegetation_object{}.trecim_species_popular_name_codeSpace xml_buffer, trecim_solitary_vegetation_object{}.trecim_width xml_real64, externalReference{}.externalObject xml_buffer
    -> CoorSwapper_SV
CoorSwapper_SV: CoordinateSwapper
    SWAP_TYPE = X <-> Y
    -> 2DForcer_SV
2DForcer_SV
    2D -> Counter_SV
Counter_SV
    CNT_ATTR = id
    DOMAIN = counter
    SCOPE = Global
    START = 0
    -> TreeHeight
TreeHeight: AttributeCreator
    ATTR_TABLE = SET_TO height = 2.5
    -> SV_Clipper [CANDIDATE]
SV_Clipper: Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> SolitaryVege_clip (writer SHAPEFILE_7)
SolitaryVege_clip (writer SHAPEFILE_7)
    attributes: id number(10,0), gml_name varchar(254), height number(20,10)
